;; Draw a straight line from the mid point of a straight line
(defun c:LT-LineFromMidPoint()
  (setq p1(getpoint "\n Pick First Point of the reference line")
            p2(getpoint "\n Pick Second Point of the reference line")
            p3(getpoint "\n Define the end point of the new line")
            )  
  (setq x(/ (- (car p2) (car p1)) 2.00))
  (setq y(/ (- (cadr p2) (cadr p1)) 2.00))
  (setq midpoint(list  (+ (car p1) x) (+ (cadr p1) y)))
  (command "line" p3 midpoint "")
)

;; Draw a straight line from the mid point of a straight line
(defun c:LT-LineFromThirdPoint()
  (setq p1(getpoint "\n Pick First Point of the reference line")
            p2(getpoint "\n Pick Second Point of the reference line")
            p3(getpoint "\n Define the end point of the new line")
            )  
  (setq x(/ (- (car p2) (car p1)) 3.00))
  (setq y(/ (- (cadr p2) (cadr p1)) 3.00))
  (setq thirdpoint(list  (+ (car p1) x) (+ (cadr p1) y)))
  (command "line" p3 thirdpoint "")
)

;; Draw a straight line from the point at the golden section of a straight line
(defun c:LT-LineFromGoldenSection()
  (setq p1(getpoint "\n Pick First Point of the reference line")
            p2(getpoint "\n Pick Second Point of the reference line")
            p3(getpoint "\n Define the end point of the new line")
            )  
  (setq x(* (- (car p2) (car p1)) 0.618))
  (setq y(* (- (cadr p2) (cadr p1)) 0.618))
  (setq goldenpoint(list  (+ (car p1) x) (+ (cadr p1) y)))
  (command "line" p3 goldenpoint "")
)
